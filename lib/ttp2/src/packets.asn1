Packets DEFINITIONS EXPLICIT TAGS ::= BEGIN
-- Normal packets
Standard ::= SEQUENCE {
	payload OCTET STRING
}

File ::= SEQUENCE {
	filePath OCTET STRING,
	start INTEGER,
	end INTEGER,
	payload OCTET STRING
}

ViewportRequest ::= SEQUENCE {
	xStart INTEGER,
	xEnd INTEGER,
	yStart INTEGER,
	yEnd INTEGER
}

Viewport ::= SEQUENCE {
	xStart INTEGER,
	xEnd INTEGER,
	yStart INTEGER,
	yEnd INTEGER,
	payload OCTET STRING
}

TqlQuery ::= SEQUENCE {
	query OCTET STRING
}

Error ::= SEQUENCE {
	code INTEGER,
	message OCTET STRING
}

Universal ::= SEQUENCE {
	type INTEGER,
	bytes OCTET STRING
}

-- TDFS specific
Ls ::= SEQUENCE {
	directory OCTET STRING
}

LsSolution ::= SEQUENCE {
	directoryItems SEQUENCE OF UTF8String
}

Packet ::= SEQUENCE {
	id INTEGER,
	payload CHOICE {
		standard [0] Standard,
		file [1] File,
		viewportRequest [2] ViewportRequest,
		viewport [3] Viewport,
		tqlQuery [4] TqlQuery,
		error [5] Error,
		universal [6] Universal,
		ls [7] Ls,
		lsSolution [8] LsSolution
	}
} 

END
